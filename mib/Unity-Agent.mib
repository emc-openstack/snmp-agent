Unity-MIB DEFINITIONS ::= BEGIN

IMPORTS
	Unsigned32, OBJECT-TYPE
	FROM SNMPv2-SMI

	DisplayString
	FROM SNMPv2-TC;

	-- 1.3
	org OBJECT IDENTIFIER ::= { iso 3 }
	
	-- 1.3.6
	dod OBJECT IDENTIFIER ::= { org 6 }
	
	-- 1.3.6.1
	internet OBJECT IDENTIFIER ::= { dod 1 }
	
	-- 1.3.6.1.4
	private OBJECT IDENTIFIER ::= { internet 4 }
	
	-- 1.3.6.1.4.1
	enterprises OBJECT IDENTIFIER ::= { private 1 }

	-- 1.3.6.1.4.1.1139
	emc OBJECT IDENTIFIER ::= { enterprises 1139 }
	
	-- 1.3.6.1.4.1.1139.103
	unity OBJECT IDENTIFIER ::= { emc 103 }
	
	-- 1.3.6.1.4.1.1139.103.2
	unityStorageObjects OBJECT IDENTIFIER ::= { unity 2 }
	
	-- 1.3.6.1.4.1.1139.103.2.1
	agentVersion OBJECT-TYPE
		SYNTAX DisplayString
		ACCESS read-only
		STATUS mandatory
		DESCRIPTION
			"Version of Unity SNMP Agent."
		::= { unityStorageObjects 1 }
	
	-- 1.3.6.1.4.1.1139.103.2.2
	mibVersion OBJECT-TYPE
		SYNTAX DisplayString
		ACCESS read-only
		STATUS mandatory
		DESCRIPTION
			"Description."
		::= { unityStorageObjects 2 }
	
	-- 1.3.6.1.4.1.1139.103.2.3
	manufacturer OBJECT-TYPE
		SYNTAX DisplayString
		ACCESS read-only
		STATUS mandatory
		DESCRIPTION
			"Description."
		::= { unityStorageObjects 3 }
	
	-- 1.3.6.1.4.1.1139.103.2.4
	model OBJECT-TYPE
		SYNTAX DisplayString
		ACCESS read-only
		STATUS mandatory
		DESCRIPTION
			"Description."
		::= { unityStorageObjects 4 }
	
	-- 1.3.6.1.4.1.1139.103.2.5
	serialNumber OBJECT-TYPE
		SYNTAX DisplayString
		ACCESS read-only
		STATUS mandatory
		DESCRIPTION
			"Description."
		::= { unityStorageObjects 5 }
	
	-- 1.3.6.1.4.1.1139.103.2.6
	operationEnvironmentVersion OBJECT-TYPE
		SYNTAX DisplayString
		ACCESS read-only
		STATUS mandatory
		DESCRIPTION
			"Description."
		::= { unityStorageObjects 6 }
	
	-- 1.3.6.1.4.1.1139.103.2.7
	numberOfController OBJECT-TYPE
		SYNTAX Unsigned32
		ACCESS read-only
		STATUS mandatory
		DESCRIPTION
			"Description."
		::= { unityStorageObjects 7 }
	
	-- 1.3.6.1.4.1.1139.103.2.8
	numberOfPowerSupply OBJECT-TYPE
		SYNTAX Unsigned32
		ACCESS read-only
		STATUS mandatory
		DESCRIPTION
			"Description."
		::= { unityStorageObjects 8 }
	
	-- 1.3.6.1.4.1.1139.103.2.9
	numberOfPhysicalDisk OBJECT-TYPE
		SYNTAX Unsigned32
		ACCESS read-only
		STATUS mandatory
		DESCRIPTION
			"Description."
		::= { unityStorageObjects 9 }
	
	-- 1.3.6.1.4.1.1139.103.2.10
	totalCapacity OBJECT-TYPE
		SYNTAX DisplayString
		ACCESS read-only
		STATUS mandatory
		DESCRIPTION
			"Unit: GB."
		::= { unityStorageObjects 10 }
	
	-- 1.3.6.1.4.1.1139.103.2.11
	usedCapacity OBJECT-TYPE
		SYNTAX DisplayString
		ACCESS read-only
		STATUS mandatory
		DESCRIPTION
			"Unit: GB."
		::= { unityStorageObjects 11 }
	
	-- 1.3.6.1.4.1.1139.103.2.12
	freeCapacity OBJECT-TYPE
		SYNTAX DisplayString
		ACCESS read-only
		STATUS mandatory
		DESCRIPTION
			"Unit: GB."
		::= { unityStorageObjects 12 }
	
	-- 1.3.6.1.4.1.1139.103.2.13
	totalThroughput OBJECT-TYPE
		SYNTAX DisplayString
		ACCESS read-only
		STATUS mandatory
		DESCRIPTION
			"Unit: IO/s."
		::= { unityStorageObjects 13 }
	
	-- 1.3.6.1.4.1.1139.103.2.14
	readThroughput OBJECT-TYPE
		SYNTAX DisplayString
		ACCESS read-only
		STATUS mandatory
		DESCRIPTION
			"Unit: IO/s."
		::= { unityStorageObjects 14 }
	
	-- 1.3.6.1.4.1.1139.103.2.15
	writeThroughput OBJECT-TYPE
		SYNTAX DisplayString
		ACCESS read-only
		STATUS mandatory
		DESCRIPTION
			"Unit: IO/s."
		::= { unityStorageObjects 15 }
		
	-- 1.3.6.1.4.1.1139.103.2.16
	totalBandwidth OBJECT-TYPE
		SYNTAX DisplayString
		ACCESS read-only
		STATUS mandatory
		DESCRIPTION
			"Unit: MB/s."
		::= { unityStorageObjects 16 }
	
	-- 1.3.6.1.4.1.1139.103.2.17
	readBandwidth OBJECT-TYPE
		SYNTAX DisplayString
		ACCESS read-only
		STATUS mandatory
		DESCRIPTION
			"Unit: MB/s."
		::= { unityStorageObjects 17 }
	
	-- 1.3.6.1.4.1.1139.103.2.18
	writeBandwidth OBJECT-TYPE
		SYNTAX DisplayString
		ACCESS read-only
		STATUS mandatory
		DESCRIPTION
			"Unit: MB/s."
		::= { unityStorageObjects 18 }
	
	-- 1.3.6.1.4.1.1139.103.2.19
	unityStorageControllerTable OBJECT-TYPE
		SYNTAX SEQUENCE OF UnityStorageControllerEntry
		ACCESS not-accessible
		STATUS mandatory
		DESCRIPTION
			"Description."
		::= { unityStorageObjects 19 }
	
	-- 1.3.6.1.4.1.1139.103.2.19.1
	unityStorageControllerEntry OBJECT-TYPE
		SYNTAX UnityStorageControllerEntry
		ACCESS not-accessible
		STATUS mandatory
		DESCRIPTION
			"Description."
		INDEX { controllerName }
		::= { unityStorageControllerTable 1 }
	
	UnityStorageControllerEntry ::=
		SEQUENCE { 
			controllerName
				DisplayString,
			controllerManagementIP
				DisplayString,
			controllerSerialNumber
				DisplayString,
			controllerNumberOfDAE
				Unsigned32,
			controllerNumberOfFrontendPort
				Unsigned32,
			controllerNumberOfBackendPort
				Unsigned32,
			controllerOperationalState
				DisplayString,
			controllerCpuUtilization
				DisplayString,
		    controllerTotalThroughput
				DisplayString,
			controllerReadThroughput
				DisplayString,
			controllerWriteThroughput
				DisplayString,
			controllerTotalBandwidth
				DisplayString,
			controllerReadBandwidth
				DisplayString,
			controllerWriteBandwidth
				DisplayString,
			controllerDirtyCachePagesAmount
				DisplayString,
			controllerPercentDirtyCachePages
				DisplayString,
			controllerReadCacheState
				DisplayString,
			controllerWriteCacheState
				DisplayString
		 }
	
	-- 1.3.6.1.4.1.1139.103.2.19.1.1
	controllerName OBJECT-TYPE
		SYNTAX DisplayString
		ACCESS read-only
		STATUS mandatory
		DESCRIPTION
			"Description."
		::= { unityStorageControllerEntry 1 }
	
	-- 1.3.6.1.4.1.1139.103.2.19.1.2
	controllerManagementIP OBJECT-TYPE
		SYNTAX DisplayString
		ACCESS read-only
		STATUS mandatory
		DESCRIPTION
			"Description."
		::= { unityStorageControllerEntry 2 }
	
	-- 1.3.6.1.4.1.1139.103.2.19.1.3
	controllerSerialNumber OBJECT-TYPE
		SYNTAX DisplayString
		ACCESS read-only
		STATUS mandatory
		DESCRIPTION
			"Description."
		::= { unityStorageControllerEntry 3 }
	
	-- 1.3.6.1.4.1.1139.103.2.19.1.4
	controllerNumberOfDAE OBJECT-TYPE
		SYNTAX Unsigned32
		ACCESS read-only
		STATUS mandatory
		DESCRIPTION
			"Description."
		::= { unityStorageControllerEntry 4 }
	
	-- 1.3.6.1.4.1.1139.103.2.19.1.5
	controllerNumberOfFrontendPort OBJECT-TYPE
		SYNTAX Unsigned32
		ACCESS read-only
		STATUS mandatory
		DESCRIPTION
			"Description."
		::= { unityStorageControllerEntry 5 }
	
	-- 1.3.6.1.4.1.1139.103.2.19.1.6
	controllerNumberOfBackendPort OBJECT-TYPE
		SYNTAX Unsigned32
		ACCESS read-only
		STATUS mandatory
		DESCRIPTION
			"Description."
		::= { unityStorageControllerEntry 6 }
	
	-- 1.3.6.1.4.1.1139.103.2.19.1.7
	controllerOperationalState OBJECT-TYPE
		SYNTAX DisplayString
		ACCESS read-only
		STATUS mandatory
		DESCRIPTION
			"Description."
		::= { unityStorageControllerEntry 7 }
	
	-- 1.3.6.1.4.1.1139.103.2.19.1.8
	controllerCpuUtilization OBJECT-TYPE
		SYNTAX DisplayString
		ACCESS read-only
		STATUS mandatory
		DESCRIPTION
			"Description."
		::= { unityStorageControllerEntry 8 }

	-- 1.3.6.1.4.1.1139.103.2.19.1.9
	controllerTotalThroughput OBJECT-TYPE
		SYNTAX DisplayString
		ACCESS read-only
		STATUS mandatory
		DESCRIPTION
			"Unit: IO/s."
		::= { unityStorageControllerEntry 9 }

	-- 1.3.6.1.4.1.1139.103.2.19.1.10
	controllerReadThroughput OBJECT-TYPE
		SYNTAX DisplayString
		ACCESS read-only
		STATUS mandatory
		DESCRIPTION
			"Unit: IO/s."
		::= { unityStorageControllerEntry 10 }

	-- 1.3.6.1.4.1.1139.103.2.19.1.11
	controllerWriteThroughput OBJECT-TYPE
		SYNTAX DisplayString
		ACCESS read-only
		STATUS mandatory
		DESCRIPTION
			"Unit: IO/s."
		::= { unityStorageControllerEntry 11 }

	-- 1.3.6.1.4.1.1139.103.2.19.1.12
	controllerTotalBandwidth OBJECT-TYPE
		SYNTAX DisplayString
		ACCESS read-only
		STATUS mandatory
		DESCRIPTION
			"Unit: MB/s."
		::= { unityStorageControllerEntry 12 }

	-- 1.3.6.1.4.1.1139.103.2.19.1.13
	controllerReadBandwidth OBJECT-TYPE
		SYNTAX DisplayString
		ACCESS read-only
		STATUS mandatory
		DESCRIPTION
			"Unit: MB/s."
		::= { unityStorageControllerEntry 13 }

	-- 1.3.6.1.4.1.1139.103.2.19.1.14
	controllerWriteBandwidth OBJECT-TYPE
		SYNTAX DisplayString
		ACCESS read-only
		STATUS mandatory
		DESCRIPTION
			"Unit: MB/s."
		::= { unityStorageControllerEntry 14 }

	-- 1.3.6.1.4.1.1139.103.2.19.1.15
	controllerDirtyCachePagesAmount OBJECT-TYPE
		SYNTAX DisplayString
		ACCESS read-only
		STATUS mandatory
		DESCRIPTION
			"Unit: MB."
		::= { unityStorageControllerEntry 15 }
		
	-- 1.3.6.1.4.1.1139.103.2.19.1.16
	controllerPercentDirtyCachePages OBJECT-TYPE
		SYNTAX DisplayString
		ACCESS read-only
		STATUS mandatory
		DESCRIPTION
			"Description."
		::= { unityStorageControllerEntry 16 }
	
	-- 1.3.6.1.4.1.1139.103.2.19.1.17
	controllerReadCacheState OBJECT-TYPE
		SYNTAX DisplayString
		ACCESS read-only
		STATUS mandatory
		DESCRIPTION
			"Description."
		::= { unityStorageControllerEntry 17 }
	
	-- 1.3.6.1.4.1.1139.103.2.19.1.18
	controllerWriteCacheState OBJECT-TYPE
		SYNTAX DisplayString
		ACCESS read-only
		STATUS mandatory
		DESCRIPTION
			"Description."
		::= { unityStorageControllerEntry 18 }
	
	-- 1.3.6.1.4.1.1139.103.2.20
	unityStoragePoolTable OBJECT-TYPE
		SYNTAX SEQUENCE OF UnityStoragePoolEntry
		ACCESS read-only
		STATUS mandatory
		DESCRIPTION
			"Description."
		::= { unityStorageObjects 20 }
	
	-- 1.3.6.1.4.1.1139.103.2.20.1
	unityStoragePoolEntry OBJECT-TYPE
		SYNTAX UnityStoragePoolEntry
		ACCESS read-only
		STATUS mandatory
		DESCRIPTION
			"Description."
		INDEX { poolName }
		::= { unityStoragePoolTable 1 }
	
	UnityStoragePoolEntry ::=
		SEQUENCE { 
			poolName
				DisplayString,
			poolDiskTypes
				DisplayString,
			poolRaidLevel
				DisplayString,
			poolFastCacheStatus
				DisplayString,
			poolNumberOfPhysicalDisk
				Unsigned32,
			poolTotalCapacity
				DisplayString,
			poolRemainingCapacity
				DisplayString,
			poolUsedSpace
				DisplayString,
			poolCapacityUtilization
				DisplayString
		 }

	-- 1.3.6.1.4.1.1139.103.2.20.1.1
	poolName OBJECT-TYPE
		SYNTAX DisplayString
		ACCESS read-only
		STATUS mandatory
		DESCRIPTION
			"Description."
		::= { unityStoragePoolEntry 1 }
	
	-- 1.3.6.1.4.1.1139.103.2.20.1.2
	poolDiskTypes OBJECT-TYPE
		SYNTAX DisplayString
		ACCESS read-only
		STATUS mandatory
		DESCRIPTION
			"Description."
		::= { unityStoragePoolEntry 2 }
	
	-- 1.3.6.1.4.1.1139.103.2.20.1.3
	poolRaidLevel OBJECT-TYPE
		SYNTAX DisplayString
		ACCESS read-only
		STATUS mandatory
		DESCRIPTION
			"Description."
		::= { unityStoragePoolEntry 3 }
	
	-- 1.3.6.1.4.1.1139.103.2.20.1.4
	poolFastCacheStatus OBJECT-TYPE
		SYNTAX DisplayString
		ACCESS read-only
		STATUS mandatory
		DESCRIPTION
			"Description."
		::= { unityStoragePoolEntry 4 }
	
	-- 1.3.6.1.4.1.1139.103.2.20.1.5
	poolNumberOfPhysicalDisk OBJECT-TYPE
		SYNTAX Unsigned32
		ACCESS read-only
		STATUS mandatory
		DESCRIPTION
			"Description."
		::= { unityStoragePoolEntry 5 }
	
	-- 1.3.6.1.4.1.1139.103.2.20.1.6
	poolTotalCapacity OBJECT-TYPE
		SYNTAX DisplayString
		ACCESS read-only
		STATUS mandatory
		DESCRIPTION
			"Unit: GB."
		::= { unityStoragePoolEntry 6 }
	
	-- 1.3.6.1.4.1.1139.103.2.20.1.7
	poolRemainingCapacity OBJECT-TYPE
		SYNTAX DisplayString
		ACCESS read-only
		STATUS mandatory
		DESCRIPTION
			"Unit: GB."
		::= { unityStoragePoolEntry 7 }
	
	-- 1.3.6.1.4.1.1139.103.2.20.1.8
	poolUsedSpace OBJECT-TYPE
		SYNTAX DisplayString
		ACCESS read-only
		STATUS mandatory
		DESCRIPTION
			"Unit: GB."
		::= { unityStoragePoolEntry 8 }
	
	-- 1.3.6.1.4.1.1139.103.2.20.1.9
	poolCapacityUtilization OBJECT-TYPE
		SYNTAX DisplayString
		ACCESS read-only
		STATUS mandatory
		DESCRIPTION
			"Description."
		::= { unityStoragePoolEntry 9 }
	
	-- 1.3.6.1.4.1.1139.103.2.21
	unityStorageVolumeTable OBJECT-TYPE
		SYNTAX SEQUENCE OF UnityStorageVolumeEntry
		ACCESS read-only
		STATUS mandatory
		DESCRIPTION
			"Description."
		::= { unityStorageObjects 21 }
	
	-- 1.3.6.1.4.1.1139.103.2.21.1
	unityStorageVolumeEntry OBJECT-TYPE
		SYNTAX UnityStorageVolumeEntry
		ACCESS read-only
		STATUS mandatory
		DESCRIPTION
			"Description."
		INDEX { volumeId }
		::= { unityStorageVolumeTable 1 }
	
	UnityStorageVolumeEntry ::=
		SEQUENCE { 
			volumeId
				DisplayString,
			volumeName
				DisplayString,
			volumeRaidLevel
				DisplayString,
			volumeSize
				DisplayString,
			volumeNumberOfPhysicalDisk
				Unsigned32,
			volumeOperationalState
				DisplayString,
			volumeFastCacheState
				DisplayString,
			volumeDefaultController
				DisplayString,
			volumeCurrentController
				DisplayString,
			volumeResponseTime
				DisplayString,
			volumeQueueLength
				DisplayString,
			volumeTotalThroughput
				DisplayString,
			volumeReadThroughput
				DisplayString,
			volumeWriteThroughput
				DisplayString,
			volumeFastCacheReadHitIOs
				DisplayString,
			volumeFastCacheWriteHitIOs
				DisplayString,
			volumeTotalBandwidth
				DisplayString,
			volumeReadBandwidth
				DisplayString,
			volumeWriteBandwidth
				DisplayString,
			volumeFastCacheReadHitRate
				DisplayString,
			volumeFastCacheWriteHitRate
				DisplayString,
			volumeUtilization
				DisplayString,
			volumeHostInfo
				DisplayString
		 }

	-- 1.3.6.1.4.1.1139.103.2.21.1.1
	volumeId OBJECT-TYPE
		SYNTAX DisplayString
		ACCESS read-only
		STATUS mandatory
		DESCRIPTION
			"Description."
		::= { unityStorageVolumeEntry 1 }
		
	-- 1.3.6.1.4.1.1139.103.2.21.1.2
	volumeName OBJECT-TYPE
		SYNTAX DisplayString
		ACCESS read-only
		STATUS mandatory
		DESCRIPTION
			"Description."
		::= { unityStorageVolumeEntry 2 }
	
	-- 1.3.6.1.4.1.1139.103.2.21.1.3
	volumeRaidLevel OBJECT-TYPE
		SYNTAX DisplayString
		ACCESS read-only
		STATUS mandatory
		DESCRIPTION
			"Description."
		::= { unityStorageVolumeEntry 3 }
	
	-- 1.3.6.1.4.1.1139.103.2.21.1.4
	volumeSize OBJECT-TYPE
		SYNTAX DisplayString
		ACCESS read-only
		STATUS mandatory
		DESCRIPTION
			"Unit: GB."
		::= { unityStorageVolumeEntry 4 }
	
	-- 1.3.6.1.4.1.1139.103.2.21.1.5
	volumeNumberOfPhysicalDisk OBJECT-TYPE
		SYNTAX Unsigned32
		ACCESS read-only
		STATUS mandatory
		DESCRIPTION
			"Description."
		::= { unityStorageVolumeEntry 5 }
	
	-- 1.3.6.1.4.1.1139.103.2.21.1.6
	volumeOperationalState OBJECT-TYPE
		SYNTAX DisplayString
		ACCESS read-only
		STATUS mandatory
		DESCRIPTION
			"Description."
		::= { unityStorageVolumeEntry 6 }
	
	-- 1.3.6.1.4.1.1139.103.2.21.1.7
	volumeFastCacheState OBJECT-TYPE
		SYNTAX DisplayString
		ACCESS read-only
		STATUS mandatory
		DESCRIPTION
			"Description."
		::= { unityStorageVolumeEntry 7 }
	
	-- 1.3.6.1.4.1.1139.103.2.21.1.8
	volumeDefaultController OBJECT-TYPE
		SYNTAX DisplayString
		ACCESS read-only
		STATUS mandatory
		DESCRIPTION
			"Description."
		::= { unityStorageVolumeEntry 8 }
	
	-- 1.3.6.1.4.1.1139.103.2.21.1.9
	volumeCurrentController OBJECT-TYPE
		SYNTAX DisplayString
		ACCESS read-only
		STATUS mandatory
		DESCRIPTION
			"Description."
		::= { unityStorageVolumeEntry 9 }
	
	-- 1.3.6.1.4.1.1139.103.2.21.1.10
	volumeResponseTime OBJECT-TYPE
		SYNTAX DisplayString
		ACCESS read-only
		STATUS mandatory
		DESCRIPTION
			"Unit: ms."
		::= { unityStorageVolumeEntry 10 }
	
	-- 1.3.6.1.4.1.1139.103.2.21.1.11
	volumeQueueLength OBJECT-TYPE
		SYNTAX DisplayString
		ACCESS read-only
		STATUS mandatory
		DESCRIPTION
			"Description."
		::= { unityStorageVolumeEntry 11 }	
	
	-- 1.3.6.1.4.1.1139.103.2.21.1.12
	volumeTotalThroughput OBJECT-TYPE
		SYNTAX DisplayString
		ACCESS read-only
		STATUS mandatory
		DESCRIPTION
			"Unit: IO/s."
		::= { unityStorageVolumeEntry 12 }
	
	-- 1.3.6.1.4.1.1139.103.2.21.1.13
	volumeReadThroughput OBJECT-TYPE
		SYNTAX DisplayString
		ACCESS read-only
		STATUS mandatory
		DESCRIPTION
			"Unit: IO/s."
		::= { unityStorageVolumeEntry 13 }
	
	-- 1.3.6.1.4.1.1139.103.2.21.1.14
	volumeWriteThroughput OBJECT-TYPE
		SYNTAX DisplayString
		ACCESS read-only
		STATUS mandatory
		DESCRIPTION
			"Unit: IO/s."
		::= { unityStorageVolumeEntry 14 }
	
	-- 1.3.6.1.4.1.1139.103.2.21.1.15
	volumeFastCacheReadHitIOs OBJECT-TYPE
		SYNTAX DisplayString
		ACCESS read-only
		STATUS mandatory
		DESCRIPTION
			"Unit: IO."
		::= { unityStorageVolumeEntry 15 }
	
	-- 1.3.6.1.4.1.1139.103.2.21.1.16
	volumeFastCacheWriteHitIOs OBJECT-TYPE
		SYNTAX DisplayString
		ACCESS read-only
		STATUS mandatory
		DESCRIPTION
			"Unit: IO."
		::= { unityStorageVolumeEntry 16 }
	
	-- 1.3.6.1.4.1.1139.103.2.21.1.17
	volumeTotalBandwidth OBJECT-TYPE
		SYNTAX DisplayString
		ACCESS read-only
		STATUS mandatory
		DESCRIPTION
			"Unit: MB/s."
		::= { unityStorageVolumeEntry 17 }
	
	-- 1.3.6.1.4.1.1139.103.2.21.1.18
	volumeReadBandwidth OBJECT-TYPE
		SYNTAX DisplayString
		ACCESS read-only
		STATUS mandatory
		DESCRIPTION
			"Unit: MB/s."
		::= { unityStorageVolumeEntry 18 }
	
	-- 1.3.6.1.4.1.1139.103.2.21.1.19
	volumeWriteBandwidth OBJECT-TYPE
		SYNTAX DisplayString
		ACCESS read-only
		STATUS mandatory
		DESCRIPTION
			"Unit: MB/s."
		::= { unityStorageVolumeEntry 19 }
	
	-- 1.3.6.1.4.1.1139.103.2.21.1.20
	volumeFastCacheReadHitRate OBJECT-TYPE
		SYNTAX DisplayString
		ACCESS read-only
		STATUS mandatory
		DESCRIPTION
			"Description."
		::= { unityStorageVolumeEntry 20 }
	
	-- 1.3.6.1.4.1.1139.103.2.21.1.21
	volumeFastCacheWriteHitRate OBJECT-TYPE
		SYNTAX DisplayString
		ACCESS read-only
		STATUS mandatory
		DESCRIPTION
			"Description."
		::= { unityStorageVolumeEntry 21 }
	
	-- 1.3.6.1.4.1.1139.103.2.21.1.22
	volumeUtilization OBJECT-TYPE
		SYNTAX DisplayString
		ACCESS read-only
		STATUS mandatory
		DESCRIPTION
			"Description."
		::= { unityStorageVolumeEntry 22 }
		
	-- 1.3.6.1.4.1.1139.103.2.21.1.23
	volumeHostInfo OBJECT-TYPE
		SYNTAX DisplayString
		ACCESS read-only
		STATUS mandatory
		DESCRIPTION
			"Description."
		::= { unityStorageVolumeEntry 23 }
	
	-- 1.3.6.1.4.1.1139.103.2.22
	unityStorageDiskTable OBJECT-TYPE
		SYNTAX SEQUENCE OF UnityStorageDiskEntry
		ACCESS read-only
		STATUS mandatory
		DESCRIPTION
			"Description."
		::= { unityStorageObjects 22 }
	
	-- 1.3.6.1.4.1.1139.103.2.22.1
	unityStorageDiskEntry OBJECT-TYPE
		SYNTAX UnityStorageDiskEntry
		ACCESS read-only
		STATUS mandatory
		DESCRIPTION
			"Description."
		INDEX { diskName }
		::= { unityStorageDiskTable 1 }
	
	UnityStorageDiskEntry ::=
		SEQUENCE { 
			diskName
				DisplayString,
			diskModel
				DisplayString,
			diskSerialNumber
				DisplayString,
			diskFirmwareVersion
				DisplayString,
			diskType
				DisplayString,
			diskPhysicalLocation
				DisplayString,
			diskStatus
				DisplayString,
			diskRawCapacity
				DisplayString,
			diskCurrentPool
				DisplayString,
			diskResponseTime
				DisplayString,
			diskQueueLength
				DisplayString,
			diskTotalThroughput
				DisplayString,
			diskReadThroughput
				DisplayString,
			diskWriteThroughput
				DisplayString,
			diskTotalBandwidth
				DisplayString,
			diskReadBandwidth
				DisplayString,
			diskWriteBandwidth
				DisplayString,
			diskUtilization
				DisplayString
		 }

	-- 1.3.6.1.4.1.1139.103.2.22.1.1
	diskName OBJECT-TYPE
		SYNTAX DisplayString
		ACCESS read-only
		STATUS mandatory
		DESCRIPTION
			"Description."
		::= { unityStorageDiskEntry 1 }
	
	-- 1.3.6.1.4.1.1139.103.2.22.1.2
	diskModel OBJECT-TYPE
		SYNTAX DisplayString
		ACCESS read-only
		STATUS mandatory
		DESCRIPTION
			"Description."
		::= { unityStorageDiskEntry 2 }
	
	-- 1.3.6.1.4.1.1139.103.2.22.1.3
	diskSerialNumber OBJECT-TYPE
		SYNTAX DisplayString
		ACCESS read-only
		STATUS mandatory
		DESCRIPTION
			"Description."
		::= { unityStorageDiskEntry 3 }
	
	-- 1.3.6.1.4.1.1139.103.2.22.1.4
	diskFirmwareVersion OBJECT-TYPE
		SYNTAX DisplayString
		ACCESS read-only
		STATUS mandatory
		DESCRIPTION
			"Description."
		::= { unityStorageDiskEntry 4 }
	
	-- 1.3.6.1.4.1.1139.103.2.22.1.5
	diskType OBJECT-TYPE
		SYNTAX DisplayString
		ACCESS read-only
		STATUS mandatory
		DESCRIPTION
			"Description."
		::= { unityStorageDiskEntry 5 }
	
	-- 1.3.6.1.4.1.1139.103.2.22.1.6
	diskPhysicalLocation OBJECT-TYPE
		SYNTAX DisplayString
		ACCESS read-only
		STATUS mandatory
		DESCRIPTION
			"Description."
		::= { unityStorageDiskEntry 6 }
	
	-- 1.3.6.1.4.1.1139.103.2.22.1.7
	diskStatus OBJECT-TYPE
		SYNTAX DisplayString
		ACCESS read-only
		STATUS mandatory
		DESCRIPTION
			"Description."
		::= { unityStorageDiskEntry 7 }
	
	-- 1.3.6.1.4.1.1139.103.2.22.1.8
	diskRawCapacity OBJECT-TYPE
		SYNTAX DisplayString
		ACCESS read-only
		STATUS mandatory
		DESCRIPTION
			"Description."
		::= { unityStorageDiskEntry 8 }
	
	-- 1.3.6.1.4.1.1139.103.2.22.1.9
	diskCurrentPool OBJECT-TYPE
		SYNTAX DisplayString
		ACCESS read-only
		STATUS mandatory
		DESCRIPTION
			"Description."
		::= { unityStorageDiskEntry 9 }
	
	-- 1.3.6.1.4.1.1139.103.2.22.1.10
	diskResponseTime OBJECT-TYPE
		SYNTAX DisplayString
		ACCESS read-only
		STATUS mandatory
		DESCRIPTION
			"Unit: ms."
		::= { unityStorageDiskEntry 10 }
	
	-- 1.3.6.1.4.1.1139.103.2.22.1.11
	diskQueueLength OBJECT-TYPE
		SYNTAX DisplayString
		ACCESS read-only
		STATUS mandatory
		DESCRIPTION
			"Description."
		::= { unityStorageDiskEntry 11 }
	
	-- 1.3.6.1.4.1.1139.103.2.22.1.12
	diskTotalThroughput OBJECT-TYPE
		SYNTAX DisplayString
		ACCESS read-only
		STATUS mandatory
		DESCRIPTION
			"Unit: IO/s."
		::= { unityStorageDiskEntry 12 }
	
	-- 1.3.6.1.4.1.1139.103.2.22.1.13
	diskReadThroughput OBJECT-TYPE
		SYNTAX DisplayString
		ACCESS read-only
		STATUS mandatory
		DESCRIPTION
			"Unit: IO/s."
		::= { unityStorageDiskEntry 13 }
	
	-- 1.3.6.1.4.1.1139.103.2.22.1.14
	diskWriteThroughput OBJECT-TYPE
		SYNTAX DisplayString
		ACCESS read-only
		STATUS mandatory
		DESCRIPTION
			"Unit: IO/s."
		::= { unityStorageDiskEntry 14 }
	
	-- 1.3.6.1.4.1.1139.103.2.22.1.15
	diskTotalBandwidth OBJECT-TYPE
		SYNTAX DisplayString
		ACCESS read-only
		STATUS mandatory
		DESCRIPTION
			"Unit: MB/s."
		::= { unityStorageDiskEntry 15 }
	
	-- 1.3.6.1.4.1.1139.103.2.22.1.16
	diskReadBandwidth OBJECT-TYPE
		SYNTAX DisplayString
		ACCESS read-only
		STATUS mandatory
		DESCRIPTION
			"Unit: MB/s."
		::= { unityStorageDiskEntry 16 }
	
	-- 1.3.6.1.4.1.1139.103.2.22.1.17
	diskWriteBandwidth OBJECT-TYPE
		SYNTAX DisplayString
		ACCESS read-only
		STATUS mandatory
		DESCRIPTION
			"Unit: MB/s."
		::= { unityStorageDiskEntry 17 }
	
	-- 1.3.6.1.4.1.1139.103.2.22.1.18
	diskUtilization OBJECT-TYPE
		SYNTAX DisplayString
		ACCESS read-only
		STATUS mandatory
		DESCRIPTION
			"Description."
		::= { unityStorageDiskEntry 18 }
	
	-- 1.3.6.1.4.1.1139.103.2.23
	unityStoragePortTable OBJECT-TYPE
		SYNTAX SEQUENCE OF UnityStoragePortEntry
		ACCESS read-only
		STATUS mandatory
		DESCRIPTION
			"Description."
		::= { unityStorageObjects 23 }
	
	-- 1.3.6.1.4.1.1139.103.2.23.1
	unityStoragePortEntry OBJECT-TYPE
		SYNTAX UnityStoragePortEntry
		ACCESS read-only
		STATUS mandatory
		DESCRIPTION
			"Description."
		INDEX { portId }
		::= { unityStoragePortTable 1 }
	
	UnityStoragePortEntry ::=
		SEQUENCE { 
			portId
				Unsigned32,
			portName
				DisplayString,
			portAddress
				DisplayString,
			portType
				DisplayString,
			portCurrentSpeed
				DisplayString,
			portSupportedSpeed
				DisplayString,
			portStatus
				DisplayString,
			portTotalThroughput
				DisplayString,
			portReadThroughput
				DisplayString,
			portWriteThroughput
				DisplayString,
			portTotalBandwidth
				DisplayString,
			portReadBandwidth
				DisplayString,
			portWriteBandwidth
				DisplayString
		 }

	-- 1.3.6.1.4.1.1139.103.2.23.1.1
	portId OBJECT-TYPE
		SYNTAX Unsigned32
		ACCESS read-only
		STATUS mandatory
		DESCRIPTION
			"Description."
		::= { unityStoragePortEntry 1 }
	
	-- 1.3.6.1.4.1.1139.103.2.23.1.2
	portName OBJECT-TYPE
		SYNTAX DisplayString
		ACCESS read-only
		STATUS mandatory
		DESCRIPTION
			"Description."
		::= { unityStoragePortEntry 2 }
	
	-- 1.3.6.1.4.1.1139.103.2.23.1.3
	portAddress OBJECT-TYPE
		SYNTAX DisplayString
		ACCESS read-only
		STATUS mandatory
		DESCRIPTION
			"Description."
		::= { unityStoragePortEntry 3 }
	
	-- 1.3.6.1.4.1.1139.103.2.23.1.4
	portType OBJECT-TYPE
		SYNTAX DisplayString
		ACCESS read-only
		STATUS mandatory
		DESCRIPTION
			"Description."
		::= { unityStoragePortEntry 4 }
	
	-- 1.3.6.1.4.1.1139.103.2.23.1.5
	portCurrentSpeed OBJECT-TYPE
		SYNTAX DisplayString
		ACCESS read-only
		STATUS mandatory
		DESCRIPTION
			"Description."
		::= { unityStoragePortEntry 5 }
	
	-- 1.3.6.1.4.1.1139.103.2.23.1.6
	portSupportedSpeed OBJECT-TYPE
		SYNTAX DisplayString
		ACCESS read-only
		STATUS mandatory
		DESCRIPTION
			"Description."
		::= { unityStoragePortEntry 6 }
	
	-- 1.3.6.1.4.1.1139.103.2.23.1.7
	portStatus OBJECT-TYPE
		SYNTAX DisplayString
		ACCESS read-only
		STATUS mandatory
		DESCRIPTION
			"Description."
		::= { unityStoragePortEntry 7 }

	-- 1.3.6.1.4.1.1139.103.2.23.1.8
	portTotalThroughput OBJECT-TYPE
		SYNTAX DisplayString
		ACCESS read-only
		STATUS mandatory
		DESCRIPTION
			"Unit: IO/s."
		::= { unityStoragePortEntry 8 }
		
	-- 1.3.6.1.4.1.1139.103.2.23.1.9
	portReadThroughput OBJECT-TYPE
		SYNTAX DisplayString
		ACCESS read-only
		STATUS mandatory
		DESCRIPTION
			"Unit: IO/s."
		::= { unityStoragePortEntry 9 }
	
	-- 1.3.6.1.4.1.1139.103.2.23.1.10
	portWriteThroughput OBJECT-TYPE
		SYNTAX DisplayString
		ACCESS read-only
		STATUS mandatory
		DESCRIPTION
			"Unit: IO/s."
		::= { unityStoragePortEntry 10 }

	-- 1.3.6.1.4.1.1139.103.2.23.1.11
	portTotalBandwidth OBJECT-TYPE
		SYNTAX DisplayString
		ACCESS read-only
		STATUS mandatory
		DESCRIPTION
			"Unit: MB/s."
		::= { unityStoragePortEntry 11 }
	
	-- 1.3.6.1.4.1.1139.103.2.23.1.12
	portReadBandwidth OBJECT-TYPE
		SYNTAX DisplayString
		ACCESS read-only
		STATUS mandatory
		DESCRIPTION
			"Unit: MB/s"
		::= { unityStoragePortEntry 12 }
	
	-- 1.3.6.1.4.1.1139.103.2.23.1.13
	portWriteBandwidth OBJECT-TYPE
		SYNTAX DisplayString
		ACCESS read-only
		STATUS mandatory
		DESCRIPTION
			"Unit: MB/s."
		::= { unityStoragePortEntry 13 }
	
	-- 1.3.6.1.4.1.1139.103.2.24
	unityStorageHostTable OBJECT-TYPE
		SYNTAX SEQUENCE OF UnityStorageHostEntry
		ACCESS read-only
		STATUS mandatory
		DESCRIPTION
			"Description."
		::= { unityStorageObjects 24 }
	
	-- 1.3.6.1.4.1.1139.103.2.24.1
	unityStorageHostEntry OBJECT-TYPE
		SYNTAX UnityStorageHostEntry
		ACCESS read-only
		STATUS mandatory
		DESCRIPTION
			"Description."
		INDEX { hostHBAWWN }
		::= { unityStorageHostTable 1 }
	
	UnityStorageHostEntry ::=
		SEQUENCE { 
			hostName
				DisplayString,
			hostNetworkAddress
				DisplayString,
			hostHBAWWN
				DisplayString,
			hostOperationSystemVersion
				DisplayString,
			hostAssignedStorageVolumes
				DisplayString
		 }
	
	-- 1.3.6.1.4.1.1139.103.2.24.1.1
	hostName OBJECT-TYPE
		SYNTAX DisplayString
		ACCESS read-only
		STATUS mandatory
		DESCRIPTION
			"Description."
		::= { unityStorageHostEntry 1 }
	
	-- 1.3.6.1.4.1.1139.103.2.24.1.2
	hostNetworkAddress OBJECT-TYPE
		SYNTAX DisplayString
		ACCESS read-only
		STATUS mandatory
		DESCRIPTION
			"Description."
		::= { unityStorageHostEntry 2 }
	
	-- 1.3.6.1.4.1.1139.103.2.24.1.3
	hostHBAWWN OBJECT-TYPE
		SYNTAX DisplayString
		ACCESS read-only
		STATUS mandatory
		DESCRIPTION
			"Description."
		::= { unityStorageHostEntry 3 }
	
	-- 1.3.6.1.4.1.1139.103.2.24.1.4
	hostOperationSystemVersion OBJECT-TYPE
		SYNTAX DisplayString
		ACCESS read-only
		STATUS mandatory
		DESCRIPTION
			"Description."
		::= { unityStorageHostEntry 4 }
	
	-- 1.3.6.1.4.1.1139.103.2.24.1.5
	hostAssignedStorageVolumes OBJECT-TYPE
		SYNTAX DisplayString
		ACCESS read-only
		STATUS mandatory
		DESCRIPTION
			"Description."
		::= { unityStorageHostEntry 5 }


	-- 1.3.6.1.4.1.1139.103.2.25
	unityDeviceTable OBJECT-TYPE
		SYNTAX SEQUENCE OF UnityDeviceEntry
		ACCESS not-accessible
		STATUS mandatory
		DESCRIPTION
			"Description."
		::= { unityStorageObjects 25 }
	
	-- 1.3.6.1.4.1.1139.103.2.25.1
	unityDeviceEntry OBJECT-TYPE
		SYNTAX UnityDeviceEntry
		ACCESS not-accessible
		STATUS mandatory
		DESCRIPTION
			"Description."
		INDEX { deviceName }
		::= { unityDeviceTable 1 }
	
	UnityDeviceEntry ::=
		SEQUENCE { 
			deviceName
				DisplayString,
			deviceState
				DisplayString
		 }
	
	-- 1.3.6.1.4.1.1139.103.2.25.1.1
	deviceName OBJECT-TYPE
		SYNTAX DisplayString
		ACCESS read-only
		STATUS mandatory
		DESCRIPTION
			"Description."
		::= { unityDeviceEntry 1 }
	
	-- 1.3.6.1.4.1.1139.103.2.25.1.2
	deviceState OBJECT-TYPE
		SYNTAX DisplayString
		ACCESS read-only
		STATUS mandatory
		DESCRIPTION
			"Description."
		::= { unityDeviceEntry 2 }

	-- 1.3.6.1.4.1.1139.103.2.26
	unityEnclosureTable OBJECT-TYPE
		SYNTAX SEQUENCE OF UnityEnclosureEntry
		ACCESS not-accessible
		STATUS mandatory
		DESCRIPTION
			"Description."
		::= { unityStorageObjects 26 }
	
	-- 1.3.6.1.4.1.1139.103.2.26.1
	unityEnclosureEntry OBJECT-TYPE
		SYNTAX UnityEnclosureEntry
		ACCESS not-accessible
		STATUS mandatory
		DESCRIPTION
			"Description."
		INDEX { enclosureName }
		::= { unityEnclosureTable 1 }
	
	UnityEnclosureEntry ::=
		SEQUENCE { 
			enclosureName
				DisplayString,
			enclosureTemperature
				DisplayString,
			enclosureInputPower
				DisplayString
		 }
	
	-- 1.3.6.1.4.1.1139.103.2.26.1.1
	enclosureName OBJECT-TYPE
		SYNTAX DisplayString
		ACCESS read-only
		STATUS mandatory
		DESCRIPTION
			"Description."
		::= { unityEnclosureEntry 1 }
	
	-- 1.3.6.1.4.1.1139.103.2.26.1.2
	enclosureTemperature OBJECT-TYPE
		SYNTAX DisplayString
		ACCESS read-only
		STATUS mandatory
		DESCRIPTION
			"Description."
		::= { unityEnclosureEntry 2 }

	-- 1.3.6.1.4.1.1139.103.2.26.1.3
	enclosureInputPower OBJECT-TYPE
		SYNTAX DisplayString
		ACCESS read-only
		STATUS mandatory
		DESCRIPTION
			"Description."
		::= { unityEnclosureEntry 3 }			

END
